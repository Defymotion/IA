;;; DEFYMOTION - edición del DWG de planta de la etapa 1 (L3N). AutoLISP puro (AutoCAD LT 2024+).
;;; (c:defyrepl)  reemplazos de texto en TEXT/MTEXT de las capas DEFY_E1*
;;; (dfy-ren a b) renombra una capa si existe
;;; (dfy-borrar pts capa) borra lo que está totalmente dentro del polígono pts y en la capa
(setq *dfy-log* "C:/DEFYMOTION/L3N/Planos_IA/defy_editar_log.txt")
(defun dfy-pos (pat s / n m i r)
  (setq n (strlen s) m (strlen pat) i 1 r nil)
  (while (and (not r) (<= (+ i m -1) n))
    (if (= (substr s i m) pat) (setq r i))
    (setq i (1+ i)))
  r)
(defun dfy-rep (s old new / p)
  (while (setq p (dfy-pos old s))
    (setq s (strcat (substr s 1 (1- p)) new (substr s (+ p (strlen old))))))
  s)
(setq *dfy-reglas*
  (list
    (cons "MP402 girada" "girada")
    (cons "ENVOLVEDORA MP402" "ENVOLVEDORA")
    (cons "envolvedora MP402" "envolvedora")
    (cons "Envolvedora MP402" "Envolvedora")
    (cons "pasillos de transpaleta" "pasillos de paso de insumos")
    (cons "PASILLO TRANSPALETA" "PASILLO DE PASO DE INSUMOS")
    (cons "pasillo transpaleta" "pasillo de paso de insumos")
    (cons "Pasillo transpaleta" "Pasillo de paso de insumos")
    (cons "(v7) " "")
    (cons "Capas DEFY_E1_*: " "Referencias de colores: ")
    (cons "(03/11/2026)" "(04/11/2026)")
    (cons "celda A nueva (azul)" "celda A nueva con mesa giratoria de ingreso y cama de rolos de 1933 mm (azul)")
    (cons "del riel y buffer de cartones" "del riel del robot a\\U+00E9reo de pallets y buffer de cartones")))
(defun dfy-all (s / r)
  (if (dfy-pos "reja este 300 mm" s)
    (setq s "CELDA A (nueva): mesa giratoria de ingreso y cama de rolos de 1933 mm\\Ppallet con 1200 de frente"))
  (foreach r *dfy-reglas* (setq s (dfy-rep s (car r) (cdr r))))
  s)
(defun dfy-txt (ed / s)
  (setq s "")
  (foreach p ed (if (= (car p) 3) (setq s (strcat s (cdr p)))))
  (strcat s (cdr (assoc 1 ed))))
(defun dfy-set (ed s / out ins)
  (setq out nil ins nil)
  (foreach p ed
    (if (member (car p) '(1 3))
      (if (not ins)
        (progn
          (setq ins T)
          (while (> (strlen s) 250)
            (setq out (cons (cons 3 (substr s 1 250)) out) s (substr s 251)))
          (setq out (cons (cons 1 s) out))))
      (setq out (cons p out))))
  (reverse out))
(defun c:defyrepl (/ ss i e ed s s2 n f)
  (setq f (open *dfy-log* "a") n 0)
  (setq ss (ssget "_X" '((0 . "TEXT,MTEXT") (8 . "DEFY_E1*"))))
  (if ss
    (progn
      (setq i 0)
      (repeat (sslength ss)
        (setq e (ssname ss i) ed (entget e) s (dfy-txt ed) s2 (dfy-all s))
        (if (/= s s2)
          (progn
            (entmod (dfy-set ed s2))
            (setq n (1+ n))
            (write-line (strcat "texto: " (substr s2 1 150)) f)))
        (setq i (1+ i)))))
  (write-line (strcat "textos cambiados: " (itoa n)) f)
  (close f)
  (princ))
(defun dfy-ren (o n / f)
  (setq f (open *dfy-log* "a"))
  (if (and (tblsearch "LAYER" o) (not (tblsearch "LAYER" n)))
    (progn (command "_.-RENAME" "_LA" o n) (write-line (strcat "capa: " o " -> " n) f))
    (write-line (strcat "capa sin cambiar: " o) f))
  (close f)
  (princ))
(defun dfy-borrar (pts capa / ss f)
  (setq f (open *dfy-log* "a"))
  (setq ss (ssget "_WP" pts (list (cons 8 capa))))
  (if ss
    (progn (write-line (strcat "borrados en " capa ": " (itoa (sslength ss))) f) (command "_.ERASE" ss ""))
    (write-line (strcat "nada para borrar en " capa) f))
  (close f)
  (princ))
(princ)
